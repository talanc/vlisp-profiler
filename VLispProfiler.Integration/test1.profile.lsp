(setq prof:file (open "C:\\Users\\talan\\OneDrive\\Documents\\Visual Lisp\\test.profile.csv" "w"))
(write-line "Symbols # Id,StartLine,StartCol,EndLine,EndCol,Preview" prof:file)
(write-line "1,23,1,23,11,(setq i 5)" prof:file)
(write-line "2,24,1,29,4,(while ..." prof:file)
(write-line "3,24,8,24,30,(>= ..." prof:file)
(write-line "4,24,12,24,27,(setq i ..." prof:file)
(write-line "5,24,20,24,26,(1- i)" prof:file)
(write-line "6,25,3,27,10,(setq p1 ..." prof:file)
(write-line "7,25,12,25,30,(list 0 ..." prof:file)
(write-line "8,25,20,25,29,(* i 30)" prof:file)
(write-line "9,26,12,26,32,(list 200 ..." prof:file)
(write-line "10,26,22,26,31,(* i 30)" prof:file)
(write-line "11,28,3,28,29,(command \"pline\" p1 p2 \"\")" prof:file)
(write-line "" prof:file)
(write-line "Traces # Symbol,Trace,Time" prof:file)

(setq prof:symbols nil)
(setq prof:indent "")
(defun prof:write-trace (trac / time)
  (setq time (prof:time-str))
  (write-line (strcat prof:indent (car prof:symbols) "," trac "," time) prof:file)
  )
(defun prof:in (symbol)
  (setq prof:symbols (cons symbol prof:symbols))
  (prof:write-trace "In")
  (setq prof:indent (strcat prof:indent "\t"))
  nil
  )
(defun prof:out (value)
  (setq prof:indent (substr prof:indent 2))
  (prof:write-trace "Out")
  (setq prof:symbols (cdr prof:symbols))
  value
  )

(setq prof:start-time (* (getvar "TDUSRTIMER") 24 60 60 1000))
(defun prof:time-str ()
  (rtos (- (* (getvar "TDUSRTIMER") 24 60 60 1000) prof:start-time))
  )

(progn (prof:in "1") (prof:out (setq i 3)) ;|1|;)
(progn (prof:in "2") (prof:out (while (progn (prof:in "3") (prof:out (>= (progn (prof:in "4") (prof:out (setq i (progn (prof:in "5") (prof:out (1- i)) ;|5|;))) ;|4|;) 0)) ;|3|;)
  (progn (prof:in "6") (prof:out (setq p1 (progn (prof:in "7") (prof:out (list 0 (progn (prof:in "8") (prof:out (* i 30)) ;|8|;))) ;|7|;)
	p2 (progn (prof:in "9") (prof:out (list 200 (progn (prof:in "10") (prof:out (* i 30)) ;|10|;))) ;|9|;)
	)) ;|6|;)
  (progn (prof:in "11") (prof:out (command "pline" p1 p2 "")) ;|11|;)
  )) ;|2|;)

(close prof:file)
